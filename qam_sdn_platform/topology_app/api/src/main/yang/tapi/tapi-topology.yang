module tapi-topology {
    namespace "urn:onf:otcc:yang:tapi-topology";
    prefix tapi-topology;
    import tapi-common {
        prefix tapi-common;
    }
    organization "ONF OTCC (Open Transport Configuration & Control) Project";
    contact "
         Project Web: <https://urldefense.com/v3/__https://wiki.opennetworking.org/display/OTCC/TAPI__;!!OSsGDw!bx-l35NqfQHpJ8R_DmXfi2NX2ll5dMl9VbK5aS_m3ZShiVoz74Ur_yiFzE6g$ >
         Project List: <mailto:transport-api@opennetworking.org>
         Editor: Karthik Sethuraman <mailto:karthik.sethuraman@necam.com>
         Andrea Mazzin <mailto:andrea.mazzini@nokia.com>
         Arturo Mayoral <mailto:arturo.mayoral@telefonica.com>
         Nigel Davis <mailto:ndavis@ciena.com>";
    description "
        This module contains TAPI Topology Model definitions.
        Source: TapiTopology.uml
        - The TAPI YANG models included in this TAPI release are a *normative* part of the TAPI SDK.
        - The YANG specifications have been generated from the corresponding UML model using the [ONF EAGLE UML2YANG mapping tool]
          <https://urldefense.com/v3/__https://github.com/OpenNetworkingFoundation/EagleUmlYang__;!!OSsGDw!bx-l35NqfQHpJ8R_DmXfi2NX2ll5dMl9VbK5aS_m3ZShiVoz74Ur_6pxiNxl$ >
          and further edited manually to comply with the [ONF IISOMI UML2YANG mapping guidelines]
          <https://urldefense.com/v3/__https://wiki.opennetworking.org/display/OIMT/UML*-*YANG*Guidelines__;Kysr!!OSsGDw!bx-l35NqfQHpJ8R_DmXfi2NX2ll5dMl9VbK5aS_m3ZShiVoz74Ur_wxKUbJ_$ >
        - Status of YANG model artifacts can be determined by referring to the corresponding UML artifacts.
          As described in the UML models, some artifacts are considered *experimental*, and thus the corresponding YANG artifacts.
        - The ONF TAPI release process does not guarantee backward compatibility of YANG models across major versions of TAPI releases.
          The YANG model backward compatibility criteria are outlined in section 11 of <https://urldefense.com/v3/__https://tools.ietf.org/html/rfc7950__;!!OSsGDw!bx-l35NqfQHpJ8R_DmXfi2NX2ll5dMl9VbK5aS_m3ZShiVoz74Ur_zcAY1P4$ >.
          YANG models included in this release may not be backward compatible with previous TAPI releases.
        Copyright (c) 2018 Open Networking Foundation (ONF). All rights reserved.
        License: This module is distributed under the Apache License 2.0.";
    revision 2020-04-23 {
        description "ONF Transport API version 2.1.3.
                   Changes included in this TAPI release (v2.1.3) are listed in
                   <https://urldefense.com/v3/__https://github.com/OpenNetworkingFoundation/TAPI/blob/develop_v2_1/CHANGE_LOG/change-log.2.1.3.md__;!!OSsGDw!bx-l35NqfQHpJ8R_DmXfi2NX2ll5dMl9VbK5aS_m3ZShiVoz74Ur_xm1nx_D$ >";
        reference "ONF-TR-527, ONF-TR-512, ONF-TR-531, RFC 7950, RFC 6087 and ONF TAPI UML model
                  <https://urldefense.com/v3/__https://github.com/OpenNetworkingFoundation/TAPI/tree/v2.1.0/UML__;!!OSsGDw!bx-l35NqfQHpJ8R_DmXfi2NX2ll5dMl9VbK5aS_m3ZShiVoz74Ur_8UH3XnH$ >";
    }
    revision 2019-07-16 {
        description "ONF Transport API version 2.1.2.
                   Changes included in this TAPI release (v2.1.2) are listed in
                   <https://urldefense.com/v3/__https://github.com/OpenNetworkingFoundation/TAPI/blob/develop_v2_1/CHANGE_LOG/change-log.2.1.2.md__;!!OSsGDw!bx-l35NqfQHpJ8R_DmXfi2NX2ll5dMl9VbK5aS_m3ZShiVoz74Ur_0xFu4bN$ >";
        reference "ONF-TR-527, ONF-TR-512, ONF-TR-531, RFC 7950, RFC 6087 and ONF TAPI UML model
                  <https://urldefense.com/v3/__https://github.com/OpenNetworkingFoundation/TAPI/tree/v2.1.0/UML__;!!OSsGDw!bx-l35NqfQHpJ8R_DmXfi2NX2ll5dMl9VbK5aS_m3ZShiVoz74Ur_8UH3XnH$ >";
    }
    revision 2018-12-10 {
        description "ONF Transport API version 2.1.1.
                   Changes included in this TAPI release (v2.1.1) are listed in
                   <https://urldefense.com/v3/__https://github.com/OpenNetworkingFoundation/TAPI/blob/develop/CHANGE_LOG/change-log.2.1.1.md__;!!OSsGDw!bx-l35NqfQHpJ8R_DmXfi2NX2ll5dMl9VbK5aS_m3ZShiVoz74Ur__2p0od1$ >";
        reference "ONF-TR-527, ONF-TR-512, ONF-TR-531, RFC 7950, RFC 6087 and ONF TAPI UML model
                  <https://urldefense.com/v3/__https://github.com/OpenNetworkingFoundation/TAPI/tree/v2.1.0/UML__;!!OSsGDw!bx-l35NqfQHpJ8R_DmXfi2NX2ll5dMl9VbK5aS_m3ZShiVoz74Ur_8UH3XnH$ >";
    }
    revision 2018-10-16 {
        description "ONF Transport API version 2.1.0.
                   Changes included in this TAPI release (v2.1.0) are listed in
                   <https://urldefense.com/v3/__https://github.com/OpenNetworkingFoundation/TAPI/blob/develop/CHANGE_LOG/change-log.2.1.0.md__;!!OSsGDw!bx-l35NqfQHpJ8R_DmXfi2NX2ll5dMl9VbK5aS_m3ZShiVoz74Ur_4DGi8ul$ >";
        reference "ONF-TR-527, ONF-TR-512, ONF-TR-531, RFC 7950, RFC 6087 and ONF TAPI UML model
                  <https://urldefense.com/v3/__https://github.com/OpenNetworkingFoundation/TAPI/tree/v2.1.0/UML__;!!OSsGDw!bx-l35NqfQHpJ8R_DmXfi2NX2ll5dMl9VbK5aS_m3ZShiVoz74Ur_8UH3XnH$ >";
    }
    revision 2018-03-07 {
        description "ONF Transport API version 2.0.2
        This YANG module has been generated from the TAPI UML Model using the IISOMI-Eagle xmi2yang mapping tool.
        Changes in this revision: <https://urldefense.com/v3/__https://github.com/OpenNetworkingFoundation/TAPI/blob/develop/CHANGE_LOG/change-log.2.0.2.md__;!!OSsGDw!bx-l35NqfQHpJ8R_DmXfi2NX2ll5dMl9VbK5aS_m3ZShiVoz74Ur_8KlxwJZ$ >";
        reference "ONF-TR-527, ONF-TR-512, ONF-TR-531, RFC 6020, RFC 6087 and ONF TAPI UML model
                  <https://urldefense.com/v3/__https://github.com/OpenNetworkingFoundation/TAPI/tree/v2.0.2/UML__;!!OSsGDw!bx-l35NqfQHpJ8R_DmXfi2NX2ll5dMl9VbK5aS_m3ZShiVoz74Ur_-hMD5Xl$ >";
    }
    revision 2018-02-16 {
        description "ONF Transport API version 2.0.1
        This YANG module has been generated from the TAPI UML Model using the IISOMI-Eagle xmi2yang mapping tool.
        Changes in this revision: <https://urldefense.com/v3/__https://github.com/OpenNetworkingFoundation/TAPI/blob/develop/CHANGE_LOG/change-log.2.0.1.md__;!!OSsGDw!bx-l35NqfQHpJ8R_DmXfi2NX2ll5dMl9VbK5aS_m3ZShiVoz74Ur__C1vuym$ >";
        reference "ONF-TR-527, ONF-TR-512, ONF-TR-531, RFC 6020, RFC 6087 and ONF TAPI UML model
                  <https://urldefense.com/v3/__https://github.com/OpenNetworkingFoundation/TAPI/tree/v2.0.1/UML__;!!OSsGDw!bx-l35NqfQHpJ8R_DmXfi2NX2ll5dMl9VbK5aS_m3ZShiVoz74Ur_5DYNwzZ$ >";
    }
    revision 2018-01-02 {
        description "ONF Transport API version 2.0.0
        This YANG module has been generated from the TAPI UML Model using the IISOMI-Eagle xmi2yang mapping tool.
        Changes in this revision: <https://urldefense.com/v3/__https://github.com/OpenNetworkingFoundation/TAPI/blob/develop/CHANGE_LOG/change-log.2.0.0.md__;!!OSsGDw!bx-l35NqfQHpJ8R_DmXfi2NX2ll5dMl9VbK5aS_m3ZShiVoz74Ur_1xZSBRA$ >";
        reference "ONF-TR-527, ONF-TR-512, ONF-TR-531, RFC 6020, RFC 6087 and ONF TAPI UML model
                  <https://urldefense.com/v3/__https://github.com/OpenNetworkingFoundation/TAPI/tree/v2.0.0/UML__;!!OSsGDw!bx-l35NqfQHpJ8R_DmXfi2NX2ll5dMl9VbK5aS_m3ZShiVoz74Ur_xt-GtqY$ >";
    }
    augment "/tapi-common:context" {
        container topology-context {
            uses topology-context;
            description "Augments the base TAPI Context with TopologyService information";
        }
        description "Augments the base TAPI Context with TopologyService information";
    }

   /**************************
    * definitions of refrences
    **************************/
    grouping topology-ref {
        leaf topology-uuid {
            type leafref {
                path '/tapi-common:context/tapi-topology:topology-context/tapi-topology:topology/tapi-topology:uuid';
            }
            description "none";
        }
        description "none";
    }
    grouping link-ref {
        uses topology-ref;
        leaf link-uuid {
            type leafref {
                path '/tapi-common:context/tapi-topology:topology-context/tapi-topology:topology/tapi-topology:link/tapi-topology:uuid';
            }
            description "none";
        }
        description "none";
    }
    grouping node-ref {
        uses topology-ref;
        leaf node-uuid {
            type leafref {
                path '/tapi-common:context/tapi-topology:topology-context/tapi-topology:topology/tapi-topology:node/tapi-topology:uuid';
            }
            description "none";
        }
        description "none";
    }
    grouping node-edge-point-ref {
        uses node-ref;
        leaf node-edge-point-uuid {
            type leafref {
                path '/tapi-common:context/tapi-topology:topology-context/tapi-topology:topology/tapi-topology:node/tapi-topology:owned-node-edge-point/tapi-topology:uuid';
            }
            description "none";
        }
        description "none";
    }
    grouping node-rule-group-ref {
        uses node-ref;
        leaf node-rule-group-uuid {
            type leafref {
                path '/tapi-common:context/tapi-topology:topology-context/tapi-topology:topology/tapi-topology:node/tapi-topology:node-rule-group/tapi-topology:uuid';
            }
            description "none";
        }
        description "none";
    }

   /**************************
    * package object-classes
    **************************/ 
    grouping link {
        list node-edge-point {
            uses node-edge-point-ref;
            key 'topology-uuid node-uuid node-edge-point-uuid';
            min-elements 2;
            description "none";
        }
        leaf-list layer-protocol-name {
            type tapi-common:layer-protocol-name;
            config false;
            min-elements 1;
            description "none";
        }
        leaf direction {
            type tapi-common:forwarding-direction;
            description "The directionality of the Link.
                Is applicable to simple Links where all LinkEnds are BIDIRECTIONAL (the Link will be BIDIRECTIONAL) or UNIDIRECTIONAL (the Link will be UNIDIRECTIONAL).
                Is not present in more complex cases.";
        }
        container resilience-type {
            uses resilience-type;
            description "none";
        }
        uses tapi-common:resource-spec;
        uses tapi-common:admin-state-pac;
        uses tapi-common:capacity-pac;
        uses transfer-cost-pac;
        uses transfer-integrity-pac;
        uses transfer-timing-pac;
        uses risk-parameter-pac;
        uses validation-pac;
        uses layer-protocol-transition-pac;
        description "The Link object class models effective adjacency between two or more ForwardingDomains (FD). ";
    }
    grouping node {
        list owned-node-edge-point {
            key 'uuid';
            uses node-edge-point;
            description "none";
        }
        list aggregated-node-edge-point {
            uses node-edge-point-ref;
            key 'topology-uuid node-uuid node-edge-point-uuid';
            config false;
            description "none";
        }
        list node-rule-group {
            key 'uuid';
            uses node-rule-group;
            description "none";
        }
        container encap-topology {
            uses topology-ref;
            config false;
            description "none";
        }
        leaf-list layer-protocol-name {
            type tapi-common:layer-protocol-name;
            config false;
            min-elements 1;
            description "none";
        }
        uses tapi-common:resource-spec;
        uses tapi-common:admin-state-pac;
        uses tapi-common:capacity-pac;
        uses transfer-cost-pac;
        uses transfer-integrity-pac;
        uses transfer-timing-pac;
        description "The ForwardingDomain (FD) object class models the ForwardingDomain topological component which is used to effect forwarding of transport characteristic information and offers the potential to enable forwarding.
            At the lowest level of recursion, an FD (within a network element (NE)) represents a switch matrix (i.e., a fabric). Note that an NE can encompass multiple switch matrices (FDs). ";
    }
    grouping topology {
        list node {
            key 'uuid';
            uses node;
            description "none";
        }
        list link {
            key 'uuid';
            uses link;
            description "none";
        }
        leaf-list layer-protocol-name {
            type tapi-common:layer-protocol-name;
            config false;
            min-elements 1;
            description "none";
        }
        uses tapi-common:resource-spec;
        description "The ForwardingDomain (FD) object class models the ForwardingDomain topological component which is used to effect forwarding of transport characteristic information and offers the potential to enable forwarding. 
            At the lowest level of recursion, an FD (within a network element (NE)) represents a switch matrix (i.e., a fabric). Note that an NE can encompass multiple switch matrices (FDs). ";
    }
    grouping layer-protocol-transition-pac {
        leaf-list transitioned-layer-protocol-name {
            type string;
            description "Provides the ordered structure of layer protocol transitions encapsulated in the TopologicalEntity. The ordering relates to the LinkPort role.";
        }
        description "Relevant for a Link that is formed by abstracting one or more LTPs (in a stack) to focus on the flow and deemphasize the protocol transformation.
            This abstraction is relevant when considering multi-layer routing.
            The layer protocols of the LTP and the order of their application to the signal is still relevant and need to be accounted for. This is derived from the LTP spec details.
            This Pac provides the relevant abstractions of the LTPs and provides the necessary association to the LTPs involved.
            Links that included details in this Pac are often referred to as Transitional Links.";
    }
    grouping node-edge-point {
        leaf layer-protocol-name {
            type tapi-common:layer-protocol-name;
            description "none";
        }
        leaf-list supported-cep-layer-protocol-qualifier {
            type tapi-common:layer-protocol-qualifier;
            description "none";
        }
        list aggregated-node-edge-point {
            uses node-edge-point-ref;
            key 'topology-uuid node-uuid node-edge-point-uuid';
            config false;
            description "none";
        }
        list mapped-service-interface-point {
            uses tapi-common:service-interface-point-ref;
            key 'service-interface-point-uuid';
            //config false;
            description "NodeEdgePoint mapped to more than ServiceInterfacePoint (slicing/virtualizing) or a ServiceInterfacePoint mapped to more than one NodeEdgePoint (load balancing/Resilience) should be considered experimental";
        }
        leaf link-port-direction {
            type tapi-common:port-direction;
            description "The orientation of defined flow at the LinkEnd.";
        }
        leaf link-port-role {
            type tapi-common:port-role;
            config false;
            description "Each LinkEnd of the Link has a role (e.g., symmetric, hub, spoke, leaf, root)  in the context of the Link with respect to the Link function. ";
        }
        uses tapi-common:resource-spec;
        uses tapi-common:admin-state-pac;
        uses tapi-common:termination-pac;
        uses tapi-common:capacity-pac;
        description "The LogicalTerminationPoint (LTP) object class encapsulates the termination and adaptation functions of one or more transport layers.
            The structure of LTP supports all transport protocols including circuit and packet forms.";
    }
    grouping risk-parameter-pac {
        list risk-characteristic {
            key 'risk-characteristic-name';
            config false;
            min-elements 1;
            uses risk-characteristic;
            description "A list of risk characteristics for consideration in an analysis of shared risk. Each element of the list represents a specific risk consideration.";
        }
        description "The risk characteristics of a TopologicalEntity come directly from the underlying physical realization.
            The risk characteristics propagate from the physical realization to the client and from the server layer to the client layer, this propagation may be modified by protection.
            A TopologicalEntity may suffer degradation or failure as a result of a problem in a part of the underlying realization.
            The realization can be partitioned into segments which have some relevant common failure modes.
            There is a risk of failure/degradation of each segment of the underlying realization.
            Each segment is a part of a larger physical/geographical unit that behaves as one with respect to failure (i.e. a failure will have a high probability of impacting the whole unit (e.g. all cables in the same duct).
            Disruptions to that larger physical/geographical unit will impact (cause failure/errors to) all TopologicalEntities that use any part of that larger physical/geographical entity.
            Any TopologicalEntity that uses any part of that larger physical/geographical unit will suffer impact and hence each TopologicalEntity shares risk.
            The identifier of each physical/geographical unit that is involved in the realization of each segment of a Topological entity can be listed in the RiskParameter_Pac of that TopologicalEntity.
            A segment has one or more risk characteristic.
            Shared risk between two TopologicalEntities compromises the integrity of any solution that use one of those TopologicalEntity as a backup for the other.
            Where two TopologicalEntities have a common risk characteristic they have an elevated probability of failing simultaneously compared to two TopologicalEntities that do not share risk characteristics.";
    }
    grouping transfer-cost-pac {
        list cost-characteristic {
            key 'cost-name';
            config false;
            min-elements 1;
            uses cost-characteristic;
            description "The list of costs where each cost relates to some aspect of the TopologicalEntity.";
        }
        description "The cost characteristics of a TopologicalEntity not necessarily correlated to the cost of the underlying physical realization.
            They may be quite specific to the individual TopologicalEntity e.g. opportunity cost. Relates to layer capacity.
            There may be many perspectives from which cost may be considered  for a particular TopologicalEntity and hence many specific costs and potentially cost algorithms.
            Using an entity will incur a cost. ";
    }
    grouping transfer-integrity-pac {
        leaf error-characteristic {
            type string;
            config false;
            description "Describes the degree to which the signal propagated can be errored.
                Applies to TDM systems as the errored signal will be propagated and not packet as errored packets will be discarded.";
        }
        leaf loss-characteristic {
            type string;
            config false;
            description "Describes the acceptable characteristic of lost packets where loss may result from discard due to errors or overflow.
                Applies to packet systems and not TDM (as for TDM errored signals are propagated unless grossly errored and overflow/underflow turns into timing slips).";
        }
        leaf repeat-delivery-characteristic {
            type string;
            config false;
            description "Primarily applies to packet systems where a packet may be delivered more than once (in fault recovery for example).
                It can also apply to TDM where several frames may be received twice due to switching in a system with a large differential propagation delay.";
        }
        leaf delivery-order-characteristic {
            type string;
            config false;
            description "Describes the degree to which packets will be delivered out of sequence.
                Does not apply to TDM as the TDM protocols maintain strict order.";
        }
        leaf unavailable-time-characteristic {
            type string;
            config false;
            description "Describes the duration for which there may be no valid signal propagated.";
        }
        leaf server-integrity-process-characteristic {
            type string;
            config false;
            description "Describes the effect of any server integrity enhancement process on the characteristics of the TopologicalEntity.";
        }
        description "Transfer intergrity characteristic covers expected/specified/acceptable characteristic of degradation of the transfered signal.
            It includes all aspects of possible degradation of signal content as well as any damage of any form to the total TopologicalEntity and to the carried signals.
            Note that the statement is of total impact to the TopologicalEntity so any partial usage of the TopologicalEntity (e.g. a signal that does not use full capacity) will only suffer its portion of the impact.";
    }
    grouping transfer-timing-pac {
        list latency-characteristic {
            key 'traffic-property-name';
            config false;
            min-elements 1;
            uses latency-characteristic;
            description "The effect on the latency of a queuing process. This only has significant effect for packet based systems and has a complex characteristic.";
        }
        description "A TopologicalEntity will suffer effects from the underlying physical realization related to the timing of the information passed by the TopologicalEntity.";
    }
    grouping validation-pac {
        list validation-mechanism {
            key 'validation-mechanism';
            config false;
            min-elements 1;
            uses validation-mechanism;
            description "Provides details of the specific validation mechanism(s) used to confirm the presence of an intended topologicalEntity.";
        }
        description "Validation covers the various adjacenct discovery and reachability verification protocols. Also may cover Information source and degree of integrity.";
    }
    grouping network-topology-service {
        list topology {
            uses topology-ref;
            key 'topology-uuid';
            config false;
            description "none";
        }
        uses tapi-common:service-spec;
        description "none";
    }
    grouping topology-context {
        container nw-topology-service {
            config false;
            uses network-topology-service;
            description "none";
        }
        list topology {
            key 'uuid';
            //config false;
            uses topology;
            description "none";
        }
        description "none";
    }
    grouping inter-rule-group {
        list rule {
            key 'local-id';
            min-elements 1;
            uses rule;
            description "The list of rules of the InterRuleGroup.";
        }
        list associated-node-rule-group {
            uses node-rule-group-ref;
            key 'topology-uuid node-uuid node-rule-group-uuid';
            min-elements 2;
            description "The NodeRuleGroups that the InterRuleGroup constrains interconnection between.
                The CEPs of the NEPs of a referenced NodeRuleGroup can interconnect to the CEPs of the NEPs of another referenced NodeRuleGroup constrained by the rules of the InterRuleGroup.";
        }
        uses tapi-common:resource-spec;
        uses tapi-common:capacity-pac;
        uses transfer-cost-pac;
        uses transfer-timing-pac;
        uses risk-parameter-pac;
        description "Rules that apply between groups of NEPs.";
    }
    grouping node-rule-group {
        list rule {
            key 'local-id';
            min-elements 1;
            uses rule;
            description "The list of rules of the NodeRuleGroup.";
        }
        list node-edge-point {
            uses node-edge-point-ref;
            key 'topology-uuid node-uuid node-edge-point-uuid';
            min-elements 1;
            description "NEPs and their client CEPs that the rules apply to.";
        }
        list node-rule-group {
            uses node-rule-group-ref;
            key 'topology-uuid node-uuid node-rule-group-uuid';
			config false;
            description "NodeRuleGroups may be nested such that finer grained rules may be applied.
                A nested rule group should have a subset of the NEPs of the superior rule group.";
        }
        list inter-rule-group {
            key 'uuid';
            uses inter-rule-group;
			config false;
            description "Nested NodeRuleGroups may have InterRuleGroups. The Superior NodeRuleGroup contains the nested NodeRuleGroups and their associated InterRuleGroups.
                This is equivalent to the Node-Topology hierarchy.";
        }
        uses tapi-common:resource-spec;
        uses tapi-common:capacity-pac;
        uses transfer-cost-pac;
        uses transfer-timing-pac;
        uses risk-parameter-pac;
        description "Rules that apply to a group of NEPs.
            ";
    }
    grouping rule {
        leaf rule-type {
            type rule-type;
            config false;
            description "The focus of the rule.";
        }
        leaf forwarding-rule {
            type forwarding-rule;
            config false;
            description "Rule that restricts the creation/deletion of a Connection between points in the node rule group or related by the inter rule group between node rule groups.";
        }
        leaf override-priority {
            type uint64;
            config false;
            description "The overridePriority allows for one rule in a rule group to override another.
                Priority n rules override priority n+1 rules.
                Rules of the same priority override as follows (n overrides n+1):
                1 - MustNot
                2 - Must
                3 - May
                4 - Null
                Within a rule the flexibility rules (signal, port role...) override as follows (n overriedes n+1):
                1 - Any
                2 - Same
                3 - Different
                Where there are two or more 'Same' rules, they will form an intersection where all must be met.
                ";
        }
        leaf-list cep-direction {
            type tapi-common:port-direction;
            config false;
            description "cep direction is a list of port directions that the rule applies to.
                No entry means all cep directions.";
        }
        list cep-port-role {
            uses port-role-rule;
			config false;
            description "Indicates the port role to which the rule applies. 
                The port role is interpreted in the context of the connection type which is identified by the connection spec. 
                The port role is not meaningful in the absence of a connection spec reference.
                If a node rule group carries a port role, that role applies also to the associated inter rule where the combination of the roles in the node rule groups at the ends of the inter group rule define the connection orientation.
                For example a root-and-leaf connection may be used in a node where a node rule group collects one set of NEPs has the port role 'root' and another node rule group collects another set of NEPs has the port role 'leaf' where these are joined by an inter rule group. This combination specifies an allowed orientation of the root-and-leaf connection.
                No port role statement means all port roles are allowed.";
        }
        list connection-spec-reference {
            config false;
            uses connection-spec-reference;
            description "Identifies the type of connection that the rule applies to. 
                If the attribute is not present then the rule applies to all types of connection supported by the device.";
        }
        leaf-list layer-protocol-qualifier {
            type tapi-common:layer-protocol-qualifier;
            config false;
            description "Qualifies a rule for a particular layerProtocol identifying the qualifiers that the rule apples to.
                If the attribute is not present then the rule applies to all relevant qualifiers of the layer protocol of the parent entity.";
        }
        container signal-property {
            config false;
            uses signal-property-rule;
            description "The rule only applies to signals with the properties listed. 
                If the attribute is not present then the rule applies to all signals.";
        }
        leaf-list complex-rule {
            type string;
            config false;
            description "Allows for more complex rules where the basic rule system is not sufficient.";
        }
        uses tapi-common:local-class;
        description "Single complex rule statememt.
            A Node with no rule group has no restrictions and is essentially May/Any
            A node rule group constrain the CEP connectability in the Node.
            A connection from a NEP must abide by all rules that relate to that NEP
            Rules that are for a particular layerProtocolQualifier, connectionSpecReference, cepPortRole and cepDirection combination must be abided by in combination as dictated by overridePriority.
            If a particular
            - connectionSpecReference does not have any rule statements then it is not supported and connections of that type are not possible within the rule group.
            - cepPortRole of a particular connectionSpecReference does not have any rule statements then it is not supported and connections of that connectionSpecReference (type) cannot have that cepPortRole for CEPs from NEPs in that rule group.
            - cepDirection for a particular connectionSpecReference does not have any rule statements then it is not supported and connections of that connectionSpecReference (type) cannot have that cepPortDirection for CEPs from NEPs in that rule group.
            Rules that are for different layerProtocolQualifiers or connectionSpecReferences are independent and provide options for connection in the rule group.
            Some rules may apply to multiple connectionSpecReferences and all cepPortRoles and all cepDirections.";
    }

    /**************************
    * package type-definitions
    **************************/ 
    identity PORT_ROLE_RULE_OPTION {
        description "none";
    }
    identity PORT_ROLE_RULE_OPTION_SAME_ROLE {
        base PORT_ROLE_RULE_OPTION;
        description "The ports of the connection to which the rule applies must have the same role from the list in port role.";
    }
    identity PORT_ROLE_RULE_OPTION_DIFFERENT_ROLE {
        base PORT_ROLE_RULE_OPTION;
        description "The ports of the connection to which the rule applies must have different roles from the list in port role.";
    }
    identity PORT_ROLE_RULE_OPTION_ANY_ROLE {
        base PORT_ROLE_RULE_OPTION;
        description "The ports of the connection to which the rule applies may take any identified role.";
    }
    identity PORT_ROLE_RULE_OPTION_NOT_ROLE {
        base PORT_ROLE_RULE_OPTION;
        description "The ports of the connection to which the rule applies must not have any of the listed roles.";
    }
    identity SIGNAL_PROPERTY_VALUE_RULE {
        description "none";
    }
    identity SIGNAL_PROPERTY_VALUE_RULE_SAME_VALUE {
        base SIGNAL_PROPERTY_VALUE_RULE;
        description "The signal property of the cep to which the rule applies must have the same value from the identied list.";
    }
    identity SIGNAL_PROPERTY_VALUE_RULE_ANY_VALUE {
        base SIGNAL_PROPERTY_VALUE_RULE;
        description "The signal property of the cep to which the rule applies may take any identified value.";
    }
    identity SIGNAL_PROPERTY_VALUE_RULE_DIFFERENT_VALUE {
        base SIGNAL_PROPERTY_VALUE_RULE;
        description "The signal property of the cep to which the rule applies each must have different values from the identified list.";
    }
    identity SIGNAL_PROPERTY_VALUE_RULE_NOT_VALUE {
        base SIGNAL_PROPERTY_VALUE_RULE;
        description "The signal property of the cep to which the rule applies must not have any of the identified values.";
    }
    grouping cost-characteristic {
        leaf cost-name {
            type string;
            description "The cost characteristic will related to some aspect of the TopologicalEntity (e.g. $ cost, routing weight). This aspect will be conveyed by the costName.";
        }
        leaf cost-value {
            type string;
            description "The specific cost.";
        }
        leaf cost-algorithm {
            type string;
            description "The cost may vary based upon some properties of the TopologicalEntity. The rules for the variation are conveyed by the costAlgorithm.";
        }
        description "The information for a particular cost characteristic.";
    }
    grouping latency-characteristic {
        leaf traffic-property-name {
            type string;
            description "The identifier of the specific traffic property to which the queuing latency applies.";
        }
        leaf fixed-latency-characteristic {
            type string;
            description "A TopologicalEntity suffers delay caused by the realization of the servers (e.g. distance related; FEC encoding etc.) along with some client specific processing. This is the total average latency effect of the TopologicalEntity";
        }
        leaf queing-latency-characteristic {
            type string;
            description "The specific queuing latency for the traffic property.";
        }
        leaf jitter-characteristic {
            type string;
            description "High frequency deviation from true periodicity of a signal and therefore a small high rate of change of transfer latency.
                Applies to TDM systems (and not packet).";
        }
        leaf wander-characteristic {
            type string;
            description "Low frequency deviation from true periodicity of a signal and therefore a small low rate of change of transfer latency.
                Applies to TDM systems (and not packet).";
        }
        description "Provides information on latency characteristic for a particular stated trafficProperty.";
    }
    grouping risk-characteristic {
        leaf risk-characteristic-name {
            type string;
            description "The name of the risk characteristic. The characteristic may be related to a specific degree of closeness.
                For example a particular characteristic may apply to failures that are localized (e.g. to one side of a road) where as another characteristic may relate to failures that have a broader impact (e.g. both sides of a road that crosses a bridge).
                Depending upon the importance of the traffic being routed different risk characteristics will be evaluated.";
        }
        leaf-list risk-identifier-list {
            type string;
            min-elements 1;
            description "A list of the identifiers of each physical/geographic unit (with the specific risk characteristic) that is related to a segment of the TopologicalEntity.";
        }
        description "The information for a particular risk characteristic where there is a list of risk identifiers related to that characteristic.";
    }
    grouping validation-mechanism {
        leaf validation-mechanism {
            type string;
            description "Name of mechanism used to validate adjacency";
        }
        leaf layer-protocol-adjacency-validated {
            type string;
            description "State of validatiion";
        }
        leaf validation-robustness {
            type string;
            description "Quality of validation (i.e. how likely is the stated validation to be invalid)";
        }
        description "Identifies the validation mechanism and describes the characteristics of that mechanism";
    }
    typedef forwarding-rule {
        type enumeration {
            enum MAY_FORWARD_ACROSS_GROUP {
                description "NEPs referenced by the node rule group (or indirectly by the inter rule group between node rule groups) may have connections created between them unless some other rule overrides this.
                    For an inter rule group points in a node rule group at one end of the inter rule group may be connected to points in an node rule group at an other end of the inter rule group.";
            }
            enum MUST_FORWARD_ACROSS_GROUP {
                description "NEPs referenced by the node rule group (or indirectly by the inter rule group between node rule groups) MUST have connections created between them unless some other rule overrides this.
                    For an inter rule group points in a node rule group at one end of the inter rule group MUST be connected to points in an node rule group at an other end of the inter rule group.";
            }
            enum CANNOT_FORWARD_ACROSS_GROUP {
                description "NEPs referenced by the node rule group (or indirectly by the inter rule group between node rule groups) MUST NOT have connections created between them.
                    For an inter rule group points in a node rule group at one end of the inter rule group MUST NOT be connected to points in an node rule group at an other end of the inter rule group.";
            }
            enum NO_STATEMENT_ON_FORWARDING {
                description "The rule group makes no statement on forwarding.";
            }
            enum INTER_CONNECTION_CONTENTION {
                description "Connections to NEPs in the rule group contend for resources based upon a constraint of some signal property.
                    For example, each connection to a NEP in the group must use a different value of the signal property from all other connections to NEPs in the rule group.
                    For example, each connection to a NEP in the group must use a same value of the signal property as all other connections to NEPs in the rule group. In this case the first connection created in the rule group sets the value and the group constraint is freed when the last connection is deleted.";
            }
        }
        description "Rule that restricts the creation/deletion of an connection between points referenced by rule groups.";
    }
    typedef rule-type {
        type enumeration {
            enum FORWARDING {
                description "The rule applies to the creation of connections.";
            }
            enum CAPACITY {
                description "The rule applies to capacity limitations.";
            }
            enum COST {
                description "The rule applies to the cost of the creation of connections.";
            }
            enum TIMING {
                description "The rule applies to timing constraints across the group.";
            }
            enum RISK {
                description "The rule applies to risk considerations across the group so as to express shared risk.";
            }
            enum GROUPING {
                description "The rule is simply for grouping related to other rules.";
            }
        }
        description "The focus of the rule.";
    }
    grouping resilience-type {
        leaf restoration-policy {
            type restoration-policy;
            description "none";
        }
        leaf protection-type {
            type protection-type;
            description "none";
        }
        description "none";
    }
    typedef restoration-policy {
        type enumeration {
            enum PER_DOMAIN_RESTORATION {
                description "none";
            }
            enum END_TO_END_RESTORATION {
                description "none";
            }
            enum NA {
                description "none";
            }
        }
        description "none";
    }
    typedef protection-type {
        type enumeration {
            enum NO_PROTECTON {
                description "none";
            }
            enum ONE_PLUS_ONE_PROTECTION {
                description "none";
            }
            enum ONE_PLUS_ONE_PROTECTION_WITH_DYNAMIC_RESTORATION {
                description "none";
            }
            enum PERMANENT_ONE_PLUS_ONE_PROTECTION {
                description "none";
            }
            enum ONE_FOR_ONE_PROTECTION {
                description "none";
            }
            enum DYNAMIC_RESTORATION {
                description "none";
            }
            enum PRE_COMPUTED_RESTORATION {
                description "none";
            }
            enum ONE_PLUS_ONE_PROTECTION_WITH_PRE_COMPUTED_RESTORATION {
                description "none";
            }
        }
        description "none";
    }
    grouping connection-spec-reference {
        leaf connection-spec-name {
            type string;
            config false;
            description "The name of the connection type spec.
                This can be used as a reference to a paper document where full formal machine interpretable specs are not supported.";
        }
        leaf connection-spec-id {
            type tapi-common:uuid;
            config false;
            description "The reference to a formal spec. 
                This reference need not be provided (e.g., where there is no formal machine interpretable spec for the type of connection).";
        }
        description "The definition of the type of connection.
            This definition will explain the flows in the connections and how they relate to the port roles.";
    }
    typedef port-role {
        type string;
        description "The role of a port in the context of the connection spec referenced in the rule.";
    }
    grouping port-role-rule {
        leaf-list port-role {
            type port-role;
            config false;
            description "The role(s) of the port(s) considered in the rule.";
        }
        leaf-list port-role-rule {
            type port-role-rule-option;
            config false;
            description "Where the rule references more than one port role or where there are rule intersections either as a result of overlay of rules or inter rule group usage indicates role matching criteria for a connection following the rules.
                For example if two port roles, 'a' and 'b', are listed and the port role rule is 'different', this means that a connection connecting points in that group must have port roles that are different for each CEP in that group.
                In the example if a connection can have n ports of role 'a' and m ports of role 'b' then a maximum of two ports can be drawn from the NEPs of the group and where there are two, one must be role 'a' and one must be role 'b'.";
        }
        description "Constrains which port roles the rule applies to.";
    }
    typedef port-role-rule-option {
        type identityref {
            base PORT_ROLE_RULE_OPTION;
        }
        description "Indicates how to interpret the port role list.";
    }
    grouping signal-property-rule {
        leaf signal-property-name {
            type string;
            config false;
            description "The name of the signal property to which the rule applies.";
        }
        leaf signal-property-value-rule {
            type signal-property-value-rule;
            config false;
            description "Indicates how the signal properties should be accounted for.";
        }
        leaf-list applicable-signal-value {
            type string;
            config false;
            description "Specific values of the signal property to which the rule applies.";
        }
        leaf number-of-signal-values {
            type uint64;
            config false;
            description "The number of instances of this specific property that can be supported by the group.";
        }
        description "Rule related to an identified signal property.";
    }
    typedef signal-property-value-rule {
        type identityref {
            base SIGNAL_PROPERTY_VALUE_RULE;
        }
        description "Indicates how to interpret the signal property value rule.";
    }

    /**************************
    * package interfaces
    **************************/ 
    rpc get-topology-details {
        description "none";
        input {
            leaf topology-id-or-name {
                type string;
                description "none";
            }
        }
        output {
            container topology {
                uses topology;
                description "none";
            }
        }
    }
    rpc get-node-details {
        description "none";
        input {
            leaf topology-id-or-name {
                type string;
                description "none";
            }
            leaf node-id-or-name {
                type string;
                description "none";
            }
        }
        output {
            container node {
                uses node;
                description "none";
            }
        }
    }
    rpc get-node-edge-point-details {
        description "none";
        input {
            leaf topology-id-or-name {
                type string;
                description "none";
            }
            leaf node-id-or-name {
                type string;
                description "none";
            }
            leaf ep-id-or-name {
                type string;
                description "none";
            }
        }
        output {
            container node-edge-point {
                uses node-edge-point;
                description "none";
            }
        }
    }
    rpc get-link-details {
        description "none";
        input {
            leaf topology-id-or-name {
                type string;
                description "none";
            }
            leaf link-id-or-name {
                type string;
                description "none";
            }
        }
        output {
            container link {
                uses link;
                description "none";
            }
        }
    }
    rpc get-topology-list {
        description "none";
        output {
            list topology {
                key 'uuid';
                uses topology;
                description "none";
            }
        }
    }

}
