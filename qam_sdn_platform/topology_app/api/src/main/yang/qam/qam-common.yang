module qam-common {

    namespace "qameleon-common";
    prefix q-common;

    organization "NXW";
    contact "p.piscione@nextworks.it";
    description "Desc";

    revision 2020-09-14{
        description "qameleon-common";
    }


typedef q-node-type {
    type enumeration {
      enum lumentum {
        value "1";
        description " Lumentum node.";
      }
      enum nll {
        value "2";
        description " Nll node.";
      }
	enum dummy {
        value "3";
        description "Dummy node.";
      }
	enum endpoint {
        value "4";
        description " Endpoint node.";
      }
	enum openroadm {
        value "5";
        description " OpenRoadm node.";
      }
      enum sbvt {
        value "6";
        description " SBVT node.";
      }
    }
    description "Type of Qameleon node";
}

grouping light-path-info{
	leaf id{
		type string;	
	}
	leaf channel-number{
		type int32;	
	}	
	leaf sip-src{
		type string;
	}
	leaf sip-dst{
		type string;
	}
}


}
